module test-module {
  namespace "urn:ietf:params:xml:ns:yang:test-module";
  prefix tm;

  organization "organization";
  description
    "example yang module";
  contact
    "example@example.org";

  container main {
    leaf enum {
      type enumeration {
        enum "yes" {
          value 1;
        }
        enum "no" {
          value 2;
        }
        enum "maybe" {
          value 3;
        }
      }
    }
    leaf options {
      type bits {
        bit strict;
        bit recursive;
        bit logging;
      }
    }
    leaf raw {
      type binary;
    }
    leaf dec64 {
      type decimal64{
         fraction-digits 2;
      }
    }
    leaf i8 {
      type int8;
    }
    leaf i16 {
      type int16;
    }
    leaf i32 {
      type int32;
    }
    leaf i64 {
      type int64;
    }
    leaf ui8 {
      type uint8;
    }
    leaf ui16 {
      type uint16;
    }
    leaf ui32 {
      type uint32;
    }
    leaf ui64 {
      type uint64;
    }
    leaf empty {
      type empty;
    }
    leaf boolean {
      type boolean;
    }
    leaf string {
      type string;
    }
    leaf id_ref {
      type identityref{
        base base_id;
      }
    }
    leaf-list numbers {
      type uint8;
    }
  }

  identity base_id;

  identity id_1 {
    base base_id;
  }

  identity id_2 {
    base base_id;
  }

  list list {
    key "key";
    leaf key {
      type string;
    }
    leaf id_ref {
      type identityref{
        base base_id;
      }
    }
    leaf union {
      type union{
          type uint8;
          type enumeration {
              enum "infinity";
          }
      }
    }
    container wireless{
        presence "wireless is enabled";
        leaf vendor_name{
          type string;
        }
    }
  }

}
