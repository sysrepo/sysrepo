module augm_by_incl_m1 {
  namespace "urn:fri:params:xml:ns:yang:augm_by_incl_m1";
  prefix abi_m1;

  import augm_by_incl_m2 {
    prefix abi_m2;
  }
  import augm_by_incl_m3 {
    prefix abi_m3;
  }

  augment "/abi_m3:cont1/abi_m3:cont11/abi_m3:cont111/abi_m2:cont1111" {
    leaf leaf1111 {
      type boolean;
    }
  }
}
