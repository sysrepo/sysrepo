module data-imp-per-D-with-identity {
    namespace "urn:test:data-imp-per-D";
    prefix dip-D;

    import data-imp-per-A {
        prefix dip-A;
    }

    import test-module {
        prefix tm;
    }

    description
        "Model to import dip-A for data import persistence test

        Includes use of imported identity";

    identity d-identity {
        base tm:base_id;
    }

    container d-cont {
        leaf d-leaf {
            type dip-A:a-type;
        }
    }
}
