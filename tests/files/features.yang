module features {
    namespace "urn:features";
    prefix feat;

    include features-sub;

    import test {
        prefix t;
    }

    feature feat1;

    feature feat3 {
        if-feature feat2;
    }

    leaf l1 {
        type string;
    }

    leaf l2 {
        if-feature feat1;
        type leafref {
            path "/t:test-leaf";
        }
    }

    leaf l3 {
        type string;
    }
}
