module test-cont-dev {
    yang-version 1.1;
    namespace "urn:test-cont-dev";
    prefix tcd;
    import test-cont {
        prefix td;
    }
    deviation /td:acls/td:attachment-points { deviate not-supported; }
}
