module rev {
    namespace "urn:rev";
    prefix r;

    revision 1970-01-01;

    leaf l {
        type empty;
    }

    container cont {
        leaf d1 {
            type string;
            default "def";
        }
    }

    notification notif;
}
