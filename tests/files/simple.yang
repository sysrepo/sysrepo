module simple {
    namespace urn:s;
    prefix s;

    container ac1 {
        leaf acd1 {
            type boolean;
            default true;
        }
        list acl1 {
            key acs1;
            leaf acs1 {
                type string;
            }
            leaf l1 {
                type string;
            }
            leaf l2 {
                type string;
            }
        }
    }
}
