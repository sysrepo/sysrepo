module mandatory {
    namespace mand;
    prefix m;
    yang-version 1.1;

    container cont {
        choice choic {
            mandatory true;
            leaf l1 {
                type empty;
            }

            anydata any2;
        }
    }
}
