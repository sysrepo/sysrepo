module ietf-interfaces-aug-leaf {
    namespace "urn:if-aug-leaf";
    prefix ial;

    yang-version 1.1;

    import ietf-interfaces {
        prefix if;
        revision-date 2014-05-08;
    }

    leaf test-leaf {
        type uint8;
    }

    augment "/if:interfaces-state/if:interface" {
        leaf new-test-leaf {
            config false;
            when "/if:interfaces-state/if:interface";
            type leafref {
                path "/ial:test-leaf";
            }
            mandatory true;
        }
    }
}
