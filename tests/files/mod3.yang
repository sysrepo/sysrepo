module mod3 {
    yang-version 1.1;
    namespace "urn:mod3";
    prefix m3;

    feature f1;

    container cont {
        leaf l1 {
            if-feature "not f1";
            type string;
            default "imback";
        }

        leaf l2 {
            if-feature f1;
            type string;
        }
    }
}
