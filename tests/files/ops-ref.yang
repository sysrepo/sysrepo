module ops-ref {
    namespace "urn:ops-ref";
    prefix or;

    feature feat1;

    leaf l1 {
        type string;
    }

    leaf l2 {
        type string;
    }

    leaf l3 {
        type string;
    }
}
