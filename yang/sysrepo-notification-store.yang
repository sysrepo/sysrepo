module sysrepo-notification-store {

  yang-version 1.1;

  namespace "urn:ietf:params:xml:ns:yang:sysrepo-notification-store";

  prefix srns;

  import ietf-yang-types {
    prefix yang;
  }

  organization "sysrepo.org";

  contact
    "sysrepo-devel@sysrepo.org";

  description
    "Event notifications that Sysrepo stores to support notification replay
    functionality. Used only internally by Sysrepo Engine.";

  revision "2016-11-22" {
    description "initial revision";
    reference "sysrepo.org";
  }

  container notifications {
    description "Holds all notifications stored in Sysrepo datastore.";

    list notification {
      key "xpath generated-time logged-time";
      description "A notification stored in Sysrepo datastore.";

      leaf xpath {
        type string;
        description "XPath of the notification.";
      }

      leaf generated-time {
        type yang:date-and-time;
        description "Time when notification was generated.";
      }

      leaf logged-time {
        type yang:timestamp;
        description "Time when notification was logged into notification store
          (in hundredths of a second since the Unix epoch, modulo 2^32).";
      }

      anydata data;
    }
  }
}
