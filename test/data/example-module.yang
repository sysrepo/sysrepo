module example-module {
   namespace "urn:ietf:params:xml:ns:yang:example";
   prefix ie;

   organization "organization";
   description  "example yang module";
   contact      "contact@example.com";

   container container {
      config true;
      list list {
         leaf leaf {
            type string;
         }
         leaf key1 {
            type string;
         }
         leaf key2 {
            type string;
         }
         key "key1 key2";
      }
   }
}
