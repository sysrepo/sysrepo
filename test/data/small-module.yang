module small-module {
  namespace "urn:ietf:params:xml:ns:yang:small-module";
  prefix sm;

  organization "organization";
  description
    "example yang module";
  contact
    "contact@example.com";

  container item{
 	leaf name {
  	  type string;
  	}
  }

  leaf size {
    type int8;
  }
}
